FME workspace cw8_zad_5_7.fmw

Parameters:
- SourceDataset_SHAPEFILE = ""$(FME_MF_DIR)warstwy\LineCSV_zad4.shp" "$(FME_MF_DIR)warstwy\T2019_KAR_POI_TABLE_zad4.shp" "$(FME_MF_DIR)warstwy\T2019_KAR_STREET_NODE_zad4.shp" "$(FME_MF_DIR)warstwy\T2019_KAR_STREETS_zad4.shp""   # Source Esri Shapefile(s)
- DestDataset_SHAPEFILE_4 = $(FME_MF_DIR)warstwy   # Destination Esri Shapefile Folder
- DestDataset_SHAPEFILE = $(FME_MF_DIR)warstwy   # Destination Esri Shapefile Folder
- DestDataset_GEOJSON_3 = $(FME_MF_DIR)warstwy\POIs_5m_2_zad6.json   # Destination GeoJSON File
- DestDataset_GEOJSON = $(FME_MF_DIR)warstwy\POIs_5m_1_zad6.json   # Destination GeoJSON File
- DestDataset_SHAPEFILE_12 = $(FME_MF_DIR)warstwy   # Destination Esri Shapefile Folder
- DestDataset_SHAPEFILE_14 = $(FME_MF_DIR)warstwy   # Destination Esri Shapefile Folder
- SourceDataset_SHAPEFILE_2 = $(FME_MF_DIR)warstwy\T2019_KAR_POI_TABLE_zad4.shp   # Source Esri Shapefile(s)
- SourceDataset_SHAPEFILE_3 = $(FME_MF_DIR)warstwy\T2019_KAR_STREET_NODE_zad4.shp   # Source Esri Shapefile(s)
- DestDataset_SHAPEFILE_7 = $(FME_MF_DIR)warstwy   # Destination Esri Shapefile Folder
- DestDataset_SHAPEFILE_16 = $(FME_MF_DIR)warstwy   # Destination Esri Shapefile Folder
- DestDataset_SHAPEFILE_13 = $(FME_MF_DIR)warstwy   # Destination Esri Shapefile Folder
- DestDataset_SHAPEFILE_15 = $(FME_MF_DIR)warstwy   # Destination Esri Shapefile Folder
- DestDataset_GEODATABASE_FILE_3 = $(FME_MF_DIR)warstwy   # File Geodatabase
- DestDataset_GEODATABASE_FILE = $(FME_MF_DIR)warstwy   # File Geodatabase

Readers:
- SHAPEFILE_1: SHAPEFILE from $(SourceDataset_SHAPEFILE) in DHDN.Berlin/Cassini
- SHAPEFILE_4: SHAPEFILE from $(SourceDataset_SHAPEFILE_2) in DHDN.Berlin/Cassini
- SHAPEFILE_7: SHAPEFILE from $(SourceDataset_SHAPEFILE_3) in DHDN.Berlin/Cassini

Writers:
- SHAPEFILE_2: SHAPEFILE to $(DestDataset_SHAPEFILE) in DHDN.Berlin/Cassini
- SHAPEFILE_3: SHAPEFILE to $(DestDataset_SHAPEFILE_4) in DHDN.Berlin/Cassini
- GEOJSON_1: GEOJSON to $(DestDataset_GEOJSON) in DHDN.Berlin/Cassini
- GEOJSON_2: GEOJSON to $(DestDataset_GEOJSON_3) in DHDN.Berlin/Cassini
- SHAPEFILE_5: SHAPEFILE to $(DestDataset_SHAPEFILE_12) in DHDN.Berlin/Cassini
- SHAPEFILE_6: SHAPEFILE to $(DestDataset_SHAPEFILE_14) in DHDN.Berlin/Cassini
- SHAPEFILE_8: SHAPEFILE to $(DestDataset_SHAPEFILE_7) in DHDN.Berlin/Cassini
- SHAPEFILE_9: SHAPEFILE to $(DestDataset_SHAPEFILE_16) in DHDN.Berlin/Cassini
- SHAPEFILE_10: SHAPEFILE to $(DestDataset_SHAPEFILE_13) in DHDN.Berlin/Cassini
- SHAPEFILE_11: SHAPEFILE to $(DestDataset_SHAPEFILE_15) in DHDN.Berlin/Cassini
- GEODATABASE_FILE_1: GEODATABASE_FILE to $(DestDataset_GEODATABASE_FILE) in DHDN.Berlin/Cassini
- GEODATABASE_FILE_2: GEODATABASE_FILE to $(DestDataset_GEODATABASE_FILE_3) in DHDN.Berlin/Cassini

T2019_KAR_STREETS_zad4 (reader SHAPEFILE_1)
    attributes: LINK_ID number(11,0), ST_NAME varchar(254), REF_IN_ID number(11,0), NREF_IN_ID number(11,0), FUNC_CLASS varchar(1), SPEED_CAT varchar(1), FR_SPEED_L number(11,0), TO_SPEED_L number(11,0), DIR_TRAVEL varchar(1)
    -> ShortestPathFinder [NETWORK]
    -> Tester
Tester
    BOOL_OP = OR
    TEST_CLAUSE = TEST @Value(DIR_TRAVEL) = T
    TEST_MODE = TEST
    PASSED -> AttributeCreator
    FAILED -> AttributeCreator_2
AttributeCreator
    ATTR_TABLE:
      SET_TO ForwardCost = 1
      SET_TO ReverseCost = 9999
    -> ShortestPathFinder_2 [NETWORK]
AttributeCreator_2
    ATTR_TABLE:
      SET_TO ForwardCost = 1
      SET_TO ReverseCost = 1
    -> ShortestPathFinder_2 [NETWORK]
LineCSV_zad4 (reader SHAPEFILE_1)
    attributes: x number(31,15), y number(31,15)
    -> ShortestPathFinder [FROM-TO]
    -> ShortestPathFinder_2 [FROM-TO]
ShortestPathFinder
    ALLOW_UTURNS = Yes
    REORDER_MODE = NONE
    SNAP_POINTS = Yes
    SNAP_TOLERANCE = 200
    WEIGHT_ATTR_CHOICE = BY_LENGTH
    PATH -> Bufferer
    PATH -> ShortestPathFinder_Path
    PATH -> Linia1 (writer SHAPEFILE_5)
    PATH -> SpatialFilter_3 [Filter]
ShortestPathFinder_Path: Inspector
Linia1 (writer SHAPEFILE_5)
    attributes: LINK_ID number(11,0), ST_NAME varchar(254), REF_IN_ID number(11,0), NREF_IN_ID number(11,0), FUNC_CLASS varchar(1), SPEED_CAT varchar(1), FR_SPEED_L number(11,0), TO_SPEED_L number(11,0), DIR_TRAVEL varchar(1)
Bufferer
    ANGLE = 22.5
    CAP_STYLE = Arc
    CORNER_STYLE = Arc
    MODE = AREA
    OFFSET = 5
    OFFSET_UNITS = METERS
    PRECISION = APPROX
    BUFFERED -> buffer1 (writer SHAPEFILE_2)
    BUFFERED -> SpatialFilter [Filter]
buffer1 (writer SHAPEFILE_2)
    attributes: LINK_ID number(11,0), ST_NAME varchar(254), REF_IN_ID number(11,0), NREF_IN_ID number(11,0), FUNC_CLASS varchar(1), SPEED_CAT varchar(1), FR_SPEED_L number(11,0), TO_SPEED_L number(11,0), DIR_TRAVEL varchar(1)
ShortestPathFinder_2
    ALLOW_UTURNS = No
    REORDER_MODE = NONE
    SNAP_POINTS = Yes
    SNAP_TOLERANCE = 200
    WEIGHT_ATTR_1 = ForwardCost
    WEIGHT_ATTR_2 = ReverseCost
    WEIGHT_ATTR_CHOICE = BY_TWO_ATTRIBUTES
    PATH -> Bufferer_2
    PATH -> Linia2 (writer SHAPEFILE_6)
    PATH -> SpatialFilter_4 [Filter]
Bufferer_2
    ANGLE = 22.5
    CAP_STYLE = Arc
    CORNER_STYLE = Arc
    MODE = AREA
    OFFSET = 5
    OFFSET_UNITS = METERS
    PRECISION = APPROX
    BUFFERED -> buffer2 (writer SHAPEFILE_3)
    BUFFERED -> SpatialFilter_2 [Filter]
buffer2 (writer SHAPEFILE_3)
    attributes: LINK_ID number(11,0), ST_NAME varchar(254), REF_IN_ID number(11,0), NREF_IN_ID number(11,0), FUNC_CLASS varchar(1), SPEED_CAT varchar(1), FR_SPEED_L number(11,0), TO_SPEED_L number(11,0), DIR_TRAVEL varchar(1)
Linia2 (writer SHAPEFILE_6)
    attributes: LINK_ID number(11,0), ST_NAME varchar(254), REF_IN_ID number(11,0), NREF_IN_ID number(11,0), FUNC_CLASS varchar(1), SPEED_CAT varchar(1), FR_SPEED_L number(11,0), TO_SPEED_L number(11,0), DIR_TRAVEL varchar(1)
T2019_KAR_POI_TABLE_zad4 (reader SHAPEFILE_4)
    attributes: POI_ID number(11,0), LINK_ID number(11,0), TYPE varchar(250), POI_NAME varchar(250), ST_NAME varchar(250), LAT number(31,15), LON number(31,15)
    -> SpatialFilter [Candidate]
    -> SpatialFilter_2 [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialFilter_Passed
    PASSED -> POIs_5m_1_zad6 (writer GEOJSON_1)
    PASSED -> POIs_5m_1_zad6 (writer SHAPEFILE_8)
SpatialFilter_Passed: Inspector
POIs_5m_1_zad6 (writer GEOJSON_1)
    attributes: POI_ID int, LINK_ID int, TYPE string, POI_NAME string, ST_NAME string, LAT float, LON float
POIs_5m_1_zad6 (writer SHAPEFILE_8)
    attributes: POI_ID number(11,0), LINK_ID number(11,0), TYPE varchar(250), POI_NAME varchar(250), ST_NAME varchar(250), LAT number(31,15), LON number(31,15)
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialFilter_2_Passed
    PASSED -> POIs_5m_2_zad6 (writer GEOJSON_2)
    PASSED -> POIs_5m_2_zad6 (writer SHAPEFILE_9)
SpatialFilter_2_Passed: Inspector
POIs_5m_2_zad6 (writer GEOJSON_2)
    attributes: POI_ID int, LINK_ID int, TYPE string, POI_NAME string, ST_NAME string, LAT float, LON float
POIs_5m_2_zad6 (writer SHAPEFILE_9)
    attributes: POI_ID number(11,0), LINK_ID number(11,0), TYPE varchar(250), POI_NAME varchar(250), ST_NAME varchar(250), LAT number(31,15), LON number(31,15)
T2019_KAR_STREET_NODE_zad4 (reader SHAPEFILE_7)
    attributes: NODE_ID number(11,0), LINK_ID number(11,0), POINT_NUM number(11,0), Z_LEVEL number(11,0), INTERSECT varchar(1), LAT number(31,15), LON number(31,15)
    -> SpatialFilter_3 [Candidate]
    -> SpatialFilter_4 [Candidate]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator
    PASSED -> skrzyzowania1_zad7 (writer SHAPEFILE_10)
    PASSED -> geobazy_Esri_1_zad7 (writer GEODATABASE_FILE_1)
StatisticsCalculator
    CALCULATION_MODE = NUMERIC
    FEAT_STATS = _total_cost,NUMERIC_MODE,MIN,MAX,COUNT,SUM,MEAN,,,,,,,,
    SUMMARY -> geobazy_Esri_1_zad7 (writer GEODATABASE_FILE_1)
    COMPLETE -> geobazy_Esri_1_zad7 (writer GEODATABASE_FILE_1)
geobazy_Esri_1_zad7 (writer GEODATABASE_FILE_1)
    attributes: NODE_ID double(11,0), LINK_ID double(11,0), POINT_NUM double(11,0), Z_LEVEL double(11,0), INTERSECT char(1), LAT double(31,15), LON double(31,15)
skrzyzowania1_zad7 (writer SHAPEFILE_10)
    attributes: NODE_ID number(11,0), LINK_ID number(11,0), POINT_NUM number(11,0), Z_LEVEL number(11,0), INTERSECT varchar(1), LAT number(31,15), LON number(31,15)
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator_2
    PASSED -> skrzyzowania2_zad7 (writer SHAPEFILE_11)
    PASSED -> geobazy_Esri_2_zad7 (writer GEODATABASE_FILE_2)
StatisticsCalculator_2
    CALCULATION_MODE = NUMERIC
    FEAT_STATS = _total_cost,NUMERIC_MODE,MIN,MAX,COUNT,SUM,MEAN,,,,,,,,
    SUMMARY -> geobazy_Esri_2_zad7 (writer GEODATABASE_FILE_2)
    COMPLETE -> geobazy_Esri_2_zad7 (writer GEODATABASE_FILE_2)
geobazy_Esri_2_zad7 (writer GEODATABASE_FILE_2)
    attributes: NODE_ID double(11,0), LINK_ID double(11,0), POINT_NUM double(11,0), Z_LEVEL double(11,0), INTERSECT char(1), LAT double(31,15), LON double(31,15)
skrzyzowania2_zad7 (writer SHAPEFILE_11)
    attributes: NODE_ID number(11,0), LINK_ID number(11,0), POINT_NUM number(11,0), Z_LEVEL number(11,0), INTERSECT varchar(1), LAT number(31,15), LON number(31,15)
