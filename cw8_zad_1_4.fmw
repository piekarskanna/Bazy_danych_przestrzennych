FME workspace cw8_zad_1_4.fmw

Parameters:
- SourceDataset_SHAPEFILE = ""$(FME_MF_DIR)Dane-cwiczenia8\T2019_KAR_GERMANY\T2019_KAR_POI_TABLE.shp" "$(FME_MF_DIR)Dane-cwiczenia8\T2019_KAR_GERMANY\T2019_KAR_STREET_NODE.shp" "$(FME_MF_DIR)Dane-cwiczenia8\T2019_KAR_GERMANY\T2019_KAR_STREETS.shp""   # Source Esri Shapefile(s)
- SourceDataset_CSV2 = $(FME_MF_DIR)Dane-cwiczenia8\routePoints.csv   # Source CSV (Comma Separated Value) File(s)
- DestDataset_SHAPEFILE_6 = $(FME_MF_DIR)warstwy   # Destination Esri Shapefile Folder
- DestDataset_SHAPEFILE_8 = $(FME_MF_DIR)warstwy   # Destination Esri Shapefile Folder
- DestDataset_SHAPEFILE_7 = $(FME_MF_DIR)warstwy   # Destination Esri Shapefile Folder
- DestDataset_SHAPEFILE = $(FME_MF_DIR)warstwy   # Destination Esri Shapefile Folder

Readers:
- SHAPEFILE_1: SHAPEFILE from $(SourceDataset_SHAPEFILE) in LL-WGS84
- CSV2_1: CSV2 from $(SourceDataset_CSV2) in LL-WGS84

Writers:
- SHAPEFILE_2: SHAPEFILE to $(DestDataset_SHAPEFILE) in DHDN.Berlin/Cassini
- SHAPEFILE_3: SHAPEFILE to $(DestDataset_SHAPEFILE_6) in DHDN.Berlin/Cassini
- SHAPEFILE_4: SHAPEFILE to $(DestDataset_SHAPEFILE_8) in DHDN.Berlin/Cassini
- SHAPEFILE_5: SHAPEFILE to $(DestDataset_SHAPEFILE_7) in DHDN.Berlin/Cassini

T2019_KAR_POI_TABLE (reader SHAPEFILE_1)
    attributes: POI_ID long, LINK_ID long, TYPE varchar(250), POI_NAME varchar(250), ST_NAME varchar(250), LAT number(31,15), LON number(31,15)
    -> Reprojector_2
Reprojector_2
    DEST = DHDN.Berlin/Cassini
    INTERPOLATION_TYPE_NAME = Nearest Neighbor
    RASTER_CELL_SIZE = Preserve Cells
    RASTER_TOLERANCE = 0.0
    SOURCE = LL-WGS84
    REPROJECTED -> T2019_KAR_POI_TABLE_zad4 (writer SHAPEFILE_3)
T2019_KAR_POI_TABLE_zad4 (writer SHAPEFILE_3)
    attributes: POI_ID long, LINK_ID long, TYPE varchar(250), POI_NAME varchar(250), ST_NAME varchar(250), LAT number(31,15), LON number(31,15)
T2019_KAR_STREET_NODE (reader SHAPEFILE_1)
    attributes: NODE_ID long, LINK_ID long, POINT_NUM long, Z_LEVEL long, INTERSECT varchar(1), LAT number(31,15), LON number(31,15)
    -> Reprojector_3
Reprojector_3
    DEST = DHDN.Berlin/Cassini
    INTERPOLATION_TYPE_NAME = Nearest Neighbor
    RASTER_CELL_SIZE = Preserve Cells
    RASTER_TOLERANCE = 0.0
    SOURCE = LL-WGS84
    REPROJECTED -> T2019_KAR_STREET_NODE_zad4 (writer SHAPEFILE_4)
T2019_KAR_STREET_NODE_zad4 (writer SHAPEFILE_4)
    attributes: NODE_ID long, LINK_ID long, POINT_NUM long, Z_LEVEL long, INTERSECT varchar(1), LAT number(31,15), LON number(31,15)
T2019_KAR_STREETS (reader SHAPEFILE_1)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_4
Reprojector_4
    DEST = DHDN.Berlin/Cassini
    INTERPOLATION_TYPE_NAME = Nearest Neighbor
    RASTER_CELL_SIZE = Preserve Cells
    RASTER_TOLERANCE = 0.0
    SOURCE = LL-WGS84
    REPROJECTED -> T2019_KAR_STREETS_zad4 (writer SHAPEFILE_5)
T2019_KAR_STREETS_zad4 (writer SHAPEFILE_5)
    attributes: LINK_ID long, ST_NAME varchar(254), REF_IN_ID long, NREF_IN_ID long, FUNC_CLASS varchar(1), SPEED_CAT varchar(1), FR_SPEED_L long, TO_SPEED_L long, DIR_TRAVEL varchar(1)
CSV (reader CSV2_1)
    attributes: x x_coordinate, y y_coordinate
    -> VertexCreator
VertexCreator
    CLOSE_LINES = Yes
    IGNORE_DUPLICATES = No
    MEASURE_TYPE = Continuous
    MISSING_VAL_MODE = Compute
    MODE_NAME = Add Point
    XVAL = @Value(x)
    YVAL = @Value(y)
    -> LineBuilder
LineBuilder
    ACCUM_INPUT_ATTRS = Use Attributes From One Feature
    REMOVE_DUPLICATES = NO
    LINE -> LineBuilder_Line
    LINE -> Reprojector
Reprojector
    DEST = DHDN.Berlin/Cassini
    INTERPOLATION_TYPE_NAME = Nearest Neighbor
    RASTER_CELL_SIZE = Preserve Cells
    RASTER_TOLERANCE = 0.0
    SOURCE = LL-WGS84
    REPROJECTED -> LineBuilder_DHDN
    REPROJECTED -> LineCSV_zad4 (writer SHAPEFILE_2)
LineCSV_zad4 (writer SHAPEFILE_2)
    attributes: x double, y double
LineBuilder_DHDN: Inspector
LineBuilder_Line: Inspector
